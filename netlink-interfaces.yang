module netlink-interfaces {
	yang-version 1.1;
	namespace "urn:netlink:yang:netlink-interfaces";
	prefix nl-if;

	import ietf-interfaces {
		prefix if;
	}

	revision 2026-09-23 {
		description "Initial revision.";
	}

	deviation "/if:interfaces/if:interface/if:enabled" {
		deviate replace {
			default "false";
		}
	}

	deviation "/if:interfaces/if:interface/if:link-up-down-trap-enable" {
		deviate not-supported;
	}

	deviation "/if:interfaces/if:interface/if:last-change" {
		deviate not-supported;
	}

	deviation "/if:interfaces/if:interface/if:higher-layer-if" {
		deviate not-supported;
	}

	deviation "/if:interfaces/if:interface/if:lower-layer-if" {
		deviate not-supported;
	}

	deviation "/if:interfaces/if:interface/if:speed" {
		deviate not-supported;
	}

	deviation "/if:interfaces/if:interface/if:statistics/if:discontinuity-time" {
		deviate not-supported;
	}

	deviation "/if:interfaces/if:interface/if:statistics/if:in-unicast-pkts" {
		deviate not-supported;
	}

	deviation "/if:interfaces/if:interface/if:statistics/if:in-broadcast-pkts" {
		deviate not-supported;
	}

	deviation "/if:interfaces/if:interface/if:statistics/if:in-multicast-pkts" {
		deviate not-supported;
	}

	deviation "/if:interfaces/if:interface/if:statistics/if:in-unknown-protos" {
		deviate not-supported;
	}

	deviation "/if:interfaces/if:interface/if:statistics/if:out-unicast-pkts" {
		deviate not-supported;
	}

	deviation "/if:interfaces/if:interface/if:statistics/if:out-broadcast-pkts" {
		deviate not-supported;
	}

	deviation "/if:interfaces/if:interface/if:statistics/if:out-multicast-pkts" {
		deviate not-supported;
	}
}
