module linux-interfaces {
	yang-version 1.1;
	namespace "urn:linux:yang:linux-interfaces";
	prefix lin-if;

	import ietf-interfaces {
		prefix if;
	}

	revision 2026-09-23 {
		description "Initial revision.";
	}

	deviation "/if:interfaces/if:interface/if:enabled" {
		deviate replace {
			default "false";
		}
	}
}
